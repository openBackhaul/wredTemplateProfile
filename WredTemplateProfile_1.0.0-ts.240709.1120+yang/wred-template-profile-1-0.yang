module wred-template-profile-1-0 {
  yang-version 1.1;
  namespace "urn:onf:yang:wred-template-profile-1-0";
  prefix wred-template-profile;

  import core-model-1-4 {
    prefix core-model;
  }

  organization
    "openBackhaul.com proposal to Open Network Modeling and Interfaces project (ONMI) at Linux Foundation (LF)";
  contact
    "WG Web : https://github.com/openBackhaul/Overview
     WG List: WredTemplateProfile@openBackhaul.com
     Editor : Thorsten Heinze
     Email  : Thorsten.Heinze@openBackhaul.com";
  description
    "Technology specific Profile definition for WRED (Weighted Random Early Detection) in dependency from traffic protocol and drop precedence.

     Copyright 2024 openBackhaul.com

     Licensed under the Apache License, Version 2.0 (the 'License');
     you may not use this file except in compliance with the License.
     You may obtain a copy of the License at
     http://www.apache.org/licenses/LICENSE-2.0
     Unless required by applicable law or agreed to in writing, software
     distributed under the License is distributed on an 'AS IS' BASIS,
     WITHOUT WARRANTIES OR CONDITIONS OF ANY KIND, either express or implied.
     See the License for the specific language governing permissions and
     limitations under the License.";

  revision 2024-07-09 {
    description
      "Model for the Transport SDN at Telefonica Germany.
       Please view https://github.com/openBackhaul/wredTemplateProfile/issues for changes.";
    reference
      "https://github.com/openBackhaul/wredTemplateProfile/tree/tsi: Model definition
       https://github.com/openBackhaul/onfCoreIm/tree/tsi: ONF TR-512 Core IM incl. Profile and enhanced Equipment definition";
  }

  identity PROFILE_NAME_TYPE_WRED_TEMPLATE_PROFILE {
    base core-model:PROFILE_NAME_TYPE;
    description
      "none";
  }

  augment "/core-model:control-construct/core-model:profile-collection/core-model:profile" {
    when "derived-from-or-self(./core-model:profile-name, 'wred-template-profile:PROFILE_NAME_TYPE_WRED_TEMPLATE_PROFILE')";
    uses wred-template-profile-spec;
    description
      "none";
  }

  /****************************************
   * grouping statements for object classes
   **************************************/ 

  grouping wred-template-profile-spec {
    container wred-template-profile-pac {
      uses wred-template-profile-pac;
      description
        "none";
    }
    description
      "none";
  }

  grouping wred-template-profile-pac {
    container wred-template-profile-capability {
      config false;
      uses wred-template-profile-capability;
      description
        "none";
    }
    container wred-template-profile-configuration {
      config false;
      uses wred-template-profile-configuration;
      description
        "none";
    }
    description
      "none";
  }

  grouping wred-template-profile-capability {
    leaf available-buffer-size {
      type int32;
      units "Byte";
      default "-1";
      config false;
      description
        "Maximum value that could be configured as thresholdHigh in Byte.";
    }
    leaf drop-probability-at-threshold-low-is-avail {
      type boolean;
      default "false";
      config false;
      description
        "true = It is possible to set a drop probability at the lower threshold.";
    }
    leaf gentle-wred-is-avail {
      type boolean;
      default "false";
      config false;
      description
        "true = The device allows activating a linear increase of drop probability between dropProbabilityAtThresholdHigh and 100% at thresholdGentle (usually drop probability jumps to 100% at thresholdHigh).";
    }
    leaf sensitivity-setting-is-avail {
      type boolean;
      default "false";
      config false;
      description
        "true = It is possible to set the sensitivity for the burst size.";
    }
    leaf coloring-is-avail {
      type boolean;
      default "false";
      config false;
      description
        "true = The device allows marking exceeding packets yellow instead of immediately discarding them.";
    }
    leaf-list supported-wred-protocol-list {
      type protocol-layer-type;
      default "PROTOCOL_LAYER_TYPE_NOT_YET_DEFINED";
      description
        "Lists the values, which could be chosen, while configuring WRED by associating a protocol with a drop precedence.";
    }
    leaf-list available-drop-precedence-kind-list {
      type drop-precedence-type;
      default "DROP_PRECEDENCE_TYPE_NOT_YET_DEFINED";
      config false;
      description
        "Explicit list (ALL not to be used here) of drop precedencies, which are available for this WRED template definition.";
    }
    description
      "none";
  }

  grouping wred-template-profile-configuration {
    list wred-template-list {
      key "affected-protocol affected-drop-precedence";
      uses wred-template-type;
      description
        "Only relevant if (droppingBehaviorKind==WRED).";
    }
    description
      "none";
  }

  /****************************************
   * typedef statements
   **************************************/ 

  typedef drop-precedence-type {
    type identityref {
      base DROP_PRECEDENCE_TYPE;
    }
    description
      "none";
  }

  typedef protocol-layer-type {
    type identityref {
      base PROTOCOL_LAYER_TYPE;
    }
    description
      "none";
  }

  /*********************************************
   * grouping statements for complex data types
   *******************************************/ 

  identity DROP_PRECEDENCE_TYPE {
    description
      "none";
  }

  identity DROP_PRECEDENCE_TYPE_ALL {
    base DROP_PRECEDENCE_TYPE;
    description
      "If all drop precedence are affected. This includes the case of drop precedencies are not implemented.";
  }

  identity DROP_PRECEDENCE_TYPE_LOW {
    base DROP_PRECEDENCE_TYPE;
    description
      "Would be equal to GREEN.";
  }

  identity DROP_PRECEDENCE_TYPE_MEDIUM {
    base DROP_PRECEDENCE_TYPE;
    description
      "Would be equal to YELLOW.";
  }

  identity DROP_PRECEDENCE_TYPE_HIGH {
    base DROP_PRECEDENCE_TYPE;
    description
      "Would be equal to RED.";
  }

  identity DROP_PRECEDENCE_TYPE_NOT_YET_DEFINED {
    base DROP_PRECEDENCE_TYPE;
    description
      "none";
  }

  identity PROTOCOL_LAYER_TYPE {
    description
      "none";
  }

  identity PROTOCOL_LAYER_TYPE_NONE {
    base PROTOCOL_LAYER_TYPE;
    description
      "none";
  }

  identity PROTOCOL_LAYER_TYPE_ETHERNET_MAC {
    base PROTOCOL_LAYER_TYPE;
    description
      "none";
  }

  identity PROTOCOL_LAYER_TYPE_VLAN {
    base PROTOCOL_LAYER_TYPE;
    description
      "none";
  }

  identity PROTOCOL_LAYER_TYPE_Q_IN_Q {
    base PROTOCOL_LAYER_TYPE;
    description
      "none";
  }

  identity PROTOCOL_LAYER_TYPE_MPLS {
    base PROTOCOL_LAYER_TYPE;
    description
      "none";
  }

  identity PROTOCOL_LAYER_TYPE_IPV4 {
    base PROTOCOL_LAYER_TYPE;
    description
      "none";
  }

  identity PROTOCOL_LAYER_TYPE_IPV6 {
    base PROTOCOL_LAYER_TYPE;
    description
      "none";
  }

  identity PROTOCOL_LAYER_TYPE_TCP {
    base PROTOCOL_LAYER_TYPE;
    description
      "none";
  }

  identity PROTOCOL_LAYER_TYPE_UDP {
    base PROTOCOL_LAYER_TYPE;
    description
      "none";
  }

  identity PROTOCOL_LAYER_TYPE_RTP {
    base PROTOCOL_LAYER_TYPE;
    description
      "none";
  }

  identity PROTOCOL_LAYER_TYPE_GTP_U {
    base PROTOCOL_LAYER_TYPE;
    description
      "none";
  }

  identity PROTOCOL_LAYER_TYPE_OTHERS {
    base PROTOCOL_LAYER_TYPE;
    description
      "none";
  }

  identity PROTOCOL_LAYER_TYPE_NOT_YET_DEFINED {
    base PROTOCOL_LAYER_TYPE;
    description
      "none";
  }

  grouping wred-template-type {
    leaf affected-protocol {
      type protocol-layer-type;
      mandatory true;
      description
        "Definition of the kind of protocol, for which the WRED profile shall apply on.";
    }
    leaf affected-drop-precedence {
      type drop-precedence-type;
      mandatory true;
      description
        "Definition of the drop precedence, for which the WRED profile shall apply on.";
    }
    container wred-configuration {
      uses wred-configuration-type;
      description
        "Associates a WRED profile to the queue, respectively drop precedence. ";
    }
    description
      "none";
  }

  grouping wred-configuration-type {
    leaf external-label {
      type string;
      default "External label not yet defined.";
      config false;
      description
        "Identifier of the instance of WredTemplateProfile. Could be a name, could be a number. Free text field to be filled by the operator.";
    }
    leaf threshold-low {
      type int32;
      units "Byte";
      default "-1";
      config false;
      description
        "Defines the lower threshold in Byte. When average queue content is exceeding this value, packets start getting dropped. Probability of dropping is linear increasing until it reaches the value configured in dropProbabilityAtThresholdHigh when average queue content reaches thresholdHigh.";
    }
    leaf drop-probability-at-threshold-low {
      type int8;
      units "%";
      default "-1";
      config false;
      description
        "Only relevant if (dropProbabilityAtLowThresholdIsAvail==true). Defines the probability (as a percentage) of an incoming packet getting dropped when the content of the queue reaches the low threshold.";
    }
    leaf threshold-high {
      type int32;
      units "Byte";
      default "-1";
      config false;
      description
        "Defines the upper threshold in Byte.  When average queue content is reaching this value, incoming packets are dropped with the probability configured in dropProbabilityAtThresholdHigh. When average queue content is exceeding this value, all incoming packets get dropped.";
    }
    leaf drop-probability-at-threshold-high {
      type int8;
      units "%";
      default "-1";
      config false;
      description
        "Defines the probability (as a percentage) of an incoming packet getting dropped when the content of the queue reaches the upper threshold.";
    }
    leaf gentle-wred-is-on {
      type boolean;
      default "false";
      config false;
      description
        "Only relevant if (gentleWredIsAvail==true). true = The drop probability is linear increasing between dropProbabilityAtThresholdHigh and 100% at thresholdGentle (otherwise drop probability jumps to 100% at thresholdHigh).";
    }
    leaf threshold-gentle {
      type int32;
      units "Byte";
      default "-1";
      config false;
      description
        "Only relevant if (gentleWredIsAvail==true) AND (gentleWredIsOn==true). Defines the 100% dropping threshold for gentle WRED in Byte.  When average queue content reaches or exceeds this value, incoming packets get dropped with 100% probability.";
    }
    leaf sensitivity {
      type int8;
      units "%";
      default "-1";
      config false;
      description
        "Only relevant if (sensitivitySettingIsAvail==true). Defines how sensitive WRED reacts on traffic burst. low values = WRED reacts quickly and is sensitive to short bursts. high values = WRED reacts slowly on short bursts, which could result in buffer overflow and tail drop. Values between 0 and 15.";
    }
    leaf coloring-is-on {
      type boolean;
      default "false";
      config false;
      description
        "Only relevant if (coloringIsAvail==true). true = Exceeding packets are marked yellow instead of being immediately discarded.";
    }
    description
      "none";
  }

  /****************************************
   * package interfaces
   **************************************/ 

  rpc create-wred-template-profile {
    description
      "none";
    output {
      leaf created-wred-template-profile {
        type leafref {
          path "/core-model:control-construct/core-model:profile-collection/core-model:profile/core-model:uuid";
          require-instance false;
        }
        mandatory true;
        description
          "UUID of the instance of WredTemplateProfile that has been newly created.";
      }
    }
  }

  rpc add-or-modify-wred-profile {
    description
      "Calling this RPC with an existing combination of values for the affectedProtocol and affectedDropPrecedence attributes overwrites the existing definition. If there is no existing WRED definition with the same combination of values for the affectedProtocol and affectedDropPrecedence, a new instance will be created.";
    input {
      leaf wred-template-profile-to-be-modified {
        type leafref {
          path "/core-model:control-construct/core-model:profile-collection/core-model:profile/core-model:uuid";
          require-instance false;
        }
        mandatory true;
        description
          "UUID of the instance of WredTemplateProfile (ProfileNameType==PROFILE_NAME_TYPE_WRED_TEMPLATE_PROFILE) that shall be modified.";
      }
      leaf affected-protocol {
        type protocol-layer-type;
        mandatory true;
        description
          "Definition of the kind of protocol, for which the WRED profile shall apply on.";
      }
      leaf affected-drop-precedence {
        type drop-precedence-type;
        mandatory true;
        description
          "Definition of the drop precedence, for which the WRED profile shall apply on.";
      }
      leaf external-label {
        type string;
        mandatory true;
        description
          "Identifier of the instance of WredTemplateProfile. Could be a name, could be a number. Free text field to be filled by the operator.";
      }
      leaf threshold-low {
        type uint64;
        mandatory true;
        description
          "Defines the lower threshold in Byte. When average queue content is exceeding this value, packets start getting dropped. Probability of dropping is linear increasing until it reaches the value configured in dropProbabilityAtThresholdHigh when average queue content reaches thresholdHigh.";
      }
      leaf drop-probability-at-threshold-low {
        type uint64;
        mandatory true;
        description
          "Only relevant if (dropProbabilityAtLowThresholdIsAvail==true). Defines the probability (as a percentage) of an incoming packet getting dropped when the content of the queue reaches the low threshold.";
      }
      leaf threshold-high {
        type uint64;
        mandatory true;
        description
          "Defines the upper threshold in Byte. When average queue content is reaching this value, incoming packets are dropped with the probability configured in dropProbabilityAtThresholdHigh. When average queue content is exceeding this value, all incoming packets get dropped.";
      }
      leaf drop-probability-at-threshold-high {
        type uint64;
        mandatory true;
        description
          "Defines the probability (as a percentage) of an incoming packet getting dropped when the content of the queue reaches the upper threshold.";
      }
      leaf gentle-wred-is-on {
        type boolean;
        mandatory true;
        description
          "Only relevant if (gentleWredIsAvail==true). true = The drop probability is linear increasing between dropProbabilityAtThresholdHigh and 100% at thresholdGentle (otherwise drop probability jumps to 100% at thresholdHigh).";
      }
      leaf threshold-gentle {
        type uint64;
        mandatory true;
        description
          "Only relevant if (gentleWredIsAvail==true) AND (gentleWredIsOn==true). Defines the 100% dropping threshold for gentle WRED in Byte. When average queue content reaches or exceeds this value, incoming packets get dropped with 100% probability.";
      }
      leaf sensitivity {
        type uint64;
        mandatory true;
        description
          "Only relevant if (sensitivitySettingIsAvail==true). Defines how sensitive WRED reacts on traffic burst. low values = WRED reacts quickly and is sensitive to short bursts. high values = WRED reacts slowly on short bursts, which could result in buffer overflow and tail drop. Values between 0 and 15.";
      }
      leaf coloring-is-on {
        type boolean;
        mandatory true;
        description
          "Only relevant if (coloringIsAvail==true). true = Exceeding packets are marked yellow instead of being immediately discarded.";
      }
    }
  }

  rpc delete-wred-profile {
    description
      "Deletes the WRED definition identified by the given combination of values of the affectedProtocol and affectedDropPrecedence attributes from the list. The instance of WredTemplateProfile that holds the entire list remains.";
    input {
      leaf wred-template-profile-to-be-modified {
        type leafref {
          path "/core-model:control-construct/core-model:profile-collection/core-model:profile/core-model:uuid";
          require-instance false;
        }
        mandatory true;
        description
          "UUID of the instance of WredTemplateProfile (ProfileNameType==PROFILE_NAME_TYPE_WRED_TEMPLATE_PROFILE) that shall be modified.";
      }
      leaf affected-protocol {
        type protocol-layer-type;
        mandatory true;
        description
          "Protocol, for which the WRED profile shall be deleted.";
      }
      leaf affected-drop-precedence {
        type drop-precedence-type;
        mandatory true;
        description
          "Drop precedence, for which the WRED profile shall be deleted.";
      }
    }
  }

  rpc delete-wred-template-profile {
    description
      "Deletes the entire instance of WredTemplateProfile, including the entire list of WRED definitions.";
    input {
      leaf obsolete-wred-template-profile {
        type leafref {
          path "/core-model:control-construct/core-model:profile-collection/core-model:profile/core-model:uuid";
          require-instance false;
        }
        mandatory true;
        description
          "UUID of the instance of WredTemplateProfile (ProfileNameType==PROFILE_NAME_TYPE_WRED_TEMPLATE_PROFILE) that shall be deleted.";
      }
    }
  }
}
